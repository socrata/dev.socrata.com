FME workspace excel2socrata_simple.fmwt
Title: excel2socrata Simple
Description: Demonstrates how to use FME Desktop to publish data to a Socrata dataset from a Microsoft Excel (.xlsx/.xls) file using the Socrata Writer.

Parameters:
- SourceDataset_XLSXR = $(FME_MF_DIR)1/Downloads/Food_Inspections_small.xlsx   # Source Microsoft Excel File(s)
- DestDataset_SOCRATA = socratau.demo.socrata.com   # Host

Readers:
- XLSXR_1: XLSXR from $(SourceDataset_XLSXR)

Writers:
- SOCRATA_1: SOCRATA to $(DestDataset_SOCRATA)

Food Inspections - small (reader XLSXR_1)
    attributes: Inspection ID number(8,0), DBA Name char(38), AKA Name char(38), License # number(8,0), Facility Type char(21), Risk char(16), Address char(25), City char(14), State char(3), Zip number(6,0), Inspection Date datetime, Inspection Type char(22), Results char(5)
    -> Food Inspections Example (writer SOCRATA_1)
Food Inspections Example (writer SOCRATA_1)
    attributes: Inspection ID number, DBA Name text, AKA Name text, License # number, Facility Type text, Risk text, Address text, City text, State text, Zip number, Inspection Date date, Inspection Type text, Results text
